# SPDX-License-Identifier: MIT
# SPDX-FileCopyrightText: 2026 Tobias Hienzsch
import FreeCAD
import FreeCADGui as Gui


def main():
    doc = FreeCAD.ActiveDocument
    links = set()
    for object in doc.Objects:
        if object.TypeId == "App::Link":
            lnk = object.LinkedObject
            if lnk.TypeId == "App::Part":
                links.add(lnk.Document)

    links.remove(doc)
    for d in sorted(links, key=lambda x: x.Name):
        print(d.Name)

    print(len(doc.getDependentDocuments()))
    print(len(links))


if __name__ == '__main__':
    main()
